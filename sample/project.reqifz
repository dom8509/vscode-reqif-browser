# Lastenheft Ladestation

# Specification: Lastenheft Ladestation

## lh-h-einleitung: Einleitung (Heading)

### LH-001 (Requirement)
Dieses Dokument beschreibt die Anforderungen an eine Wallbox für Elektrofahrzeuge.
- Status: Approved
- Priority: 3

### lh-h-begriffe: Begriffe (Heading)

#### LH-002 (Requirement)
Begriffe:
- EV: Elektrofahrzeug
- EVSE: Ladestation
- Status: Approved
- Priority: 5

## R5: Funktionale Anforderungen (Heading)

### lh-h-laden: Laden (Heading)

#### LH-010 (Requirement)
Die Ladestation muss mit bis zu 11 kW laden können.
- Status: Approved
- Priority: 1
- Verification: Test
- Safety relevant: false

#### LH-011 (Requirement)
Die Ladestation muss den Ladevorgang bei einem Fehlerstrom > 6 mA DC innerhalb von 100 ms beenden.
- Status: In Review
- Priority: 1
- Verification: Test, Analysis
- Safety relevant: true

##### LH-011.1 (Requirement)
Der Fehlerstrom muss alle 10 ms gemessen werden.
- Priority: 2
- Verification: Test
- Safety relevant: true

#### LH-012 (Requirement)
Die maximale Ladeleistung:
| Phasen | Strom | Leistung |
| --- | --- | --- |
| 1 | 16 A | 3,7 kW |
| 3 | 16 A | 11 kW |
- Status: Draft
- Priority: 2
- Verification: Review

### lh-h-bedienung: Bedienung (Heading)

#### LH-020 (Requirement)
Der Ladevorgang muss per RFID-Karte gestartet werden können.
- Status: Approved
- Priority: 2
- Verification: Test

#### LH-021 (Requirement)
Die Status-LED zeigt den Zustand an:
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- Status: Rejected
- Priority: 4

## R14: Nicht-funktionale Anforderungen (Heading)

### LH-030 (Requirement)
Schutzart mindestens IP54.
- Status: Approved
- Priority: 2
- Verification: Review
- Safety relevant: true

### LH-031 (Requirement)
Betriebstemperatur −25 °C bis +50 °C.
- Priority: 3
- Verification: Test

# Software-Anforderungen

# Specification: Software-Anforderungen

## R17: Kommunikation (Heading)

### SW-100 (Requirement)
Die Software muss OCPP 2.0.1 unterstützen.
- Status: Approved
- Priority: 1
- Verification: Test

### SW-101 (Requirement)
Verbindungsabbrüche zum Backend werden nach spätestens 30 s erkannt.
- Status: In Review
- Priority: 2
- Verification: Test

## R20: Fehlerbehandlung (Heading)

### SW-200 (Requirement)
Bei einem Fehlerstrom schaltet die Software das Schütz ab (siehe LH-011).
- Status: Draft
- Priority: 1
- Verification: Analysis
- Safety relevant: true
